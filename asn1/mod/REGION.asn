-- ^-^-^-^-^-^-^-^-^-^-^-^-^-^-^-^-^-^-^-^-^-^-^-^-^-^-^-^-
--
-- module: REGION
--
-- ^-^-^-^-^-^-^-^-^-^-^-^-^-^-^-^-^-^-^-^-^-^-^-^-^-^-^-^-

REGION {
  iso (1) standard (0) signalizedIntersection (19091) profilec (2) region (1)
  version2 (2)
}

DEFINITIONS AUTOMATIC TAGS::= BEGIN

IMPORTS

addGrpC
FROM DSRC {
  iso (1) standard (0) signalizedIntersection (19091) profilec(2) dsrc (2) version2 (2)
}

ConnectionManeuverAssist-addGrpC, ConnectionTrajectory-addGrpC,
IntersectionState-addGrpC, LaneAttributes-addGrpC, MapData-addGrpC,
MovementEvent-addGrpC, NodeAttributeSet-addGrpC, Position3D-addGrpC, RequestorDescription-addGrpC, RestrictionUserType-addGrpC, SignalStatusPackage-addGrpC
FROM AddGrpC {iso (1) standard (0) signalizedIntersection (19091) profilec(2) addgrpc (0) version2 (2)};

Reg-AdvisorySpeed ::= SEQUENCE {
  regionId  RegionId,
  regExtValue  Reg-AdvisorySpeed-regExtValue
}
Reg-AdvisorySpeed-regExtValue ::= CHOICE { ... }

Reg-ComputedLane ::= SEQUENCE {
  regionId  RegionId,
  regExtValue  Reg-ComputedLane-regExtValue
}
Reg-ComputedLane-regExtValue ::= CHOICE { ... }

Reg-ConnectionManeuverAssist ::= SEQUENCE {
  regionId  RegionId,
  regExtValue  Reg-ConnectionManeuverAssist-regExtValue
}
Reg-ConnectionManeuverAssist-regExtValue ::= CHOICE {
  addGrpC  ConnectionManeuverAssist-addGrpC,
  ...
}

Reg-GenericLane ::= SEQUENCE {
  regionId  RegionId,
  regExtValue  Reg-GenericLane-regExtValue
}
Reg-GenericLane-regExtValue ::= CHOICE {
  addGrpC  ConnectionTrajectory-addGrpC,
  ...
}

Reg-IntersectionGeometry ::= SEQUENCE {
  regionId  RegionId,
  regExtValue  Reg-IntersectionGeometry-regExtValue
}
Reg-IntersectionGeometry-regExtValue ::= CHOICE { ... }

Reg-IntersectionState ::= SEQUENCE {
  regionId  RegionId,
  regExtValue  Reg-IntersectionState-regExtValue
}
Reg-IntersectionState-regExtValue ::= CHOICE {
  addGrpC  IntersectionState-addGrpC,
  ...
}

Reg-LaneAttributes ::= SEQUENCE {
  regionId  RegionId,
  regExtValue  Reg-LaneAttributes-regExtValue
}
Reg-LaneAttributes-regExtValue ::= CHOICE {
   addGrpC  LaneAttributes-addGrpC,
   ...
}
Reg-LaneDataAttribute ::= SEQUENCE {
  regionId  RegionId,
  regExtValue  Reg-LaneDataAttribute-regExtValue
}
Reg-LaneDataAttribute-regExtValue ::= CHOICE { ... }

Reg-MapData ::= SEQUENCE {
  regionId  RegionId,
  regExtValue  Reg-MapData-regExtValue
}
Reg-MapData-regExtValue ::= CHOICE {
  addGrpC  MapData-addGrpC,
  ...
}

Reg-MovementEvent ::= SEQUENCE {
  regionId  RegionId,
  regExtValue  Reg-MovementEvent-regExtValue
}
Reg-MovementEvent-regExtValue ::= CHOICE {
   addGrpC  MovementEvent-addGrpC,
   ...
}
Reg-MovementState ::= SEQUENCE {
  regionId  RegionId,
  regExtValue  Reg-MovementState-regExtValue
}
Reg-MovementState-regExtValue ::= CHOICE { ... }

-- Reg-NodeAttributeSetLL       REG-EXT-ID-AND-TYPE ::= { ... }

Reg-NodeAttributeSetXY ::= SEQUENCE {
  regionId  RegionId,
  regExtValue  Reg-NodeAttributeSetXY-regExtValue
}
Reg-NodeAttributeSetXY-regExtValue ::= CHOICE {
  addGrpC  NodeAttributeSet-addGrpC,
  ...
}

-- Reg-NodeOffsetPointLL	   REG-EXT-ID-AND-TYPE ::= { ... }

Reg-NodeOffsetPointXY ::= SEQUENCE {
  regionId  RegionId,
  regExtValue  Reg-NodeOffsetPointXY-regExtValue
}
Reg-NodeOffsetPointXY-regExtValue ::= CHOICE { ... }

Reg-Position3D ::= SEQUENCE {
  regionId  RegionId,
  regExtValue  Reg-Position3D-regExtValue
}
Reg-Position3D-regExtValue ::= CHOICE {
  addGrpC  Position3D-addGrpC,
  ...
}

Reg-RequestorDescription ::= SEQUENCE {
  regionId  RegionId,
  regExtValue  Reg-RequestorDescription-regExtValue
}
Reg-RequestorDescription-regExtValue ::= CHOICE {
  addGrpC  RequestorDescription-addGrpC,
  ...
}

Reg-RequestorType ::= SEQUENCE {
  regionId  RegionId,
  regExtValue  Reg-RequestorType-regExtValue
}
Reg-RequestorType-regExtValue ::= CHOICE { ... }

Reg-RestrictionUserType ::= SEQUENCE {
  regionId  RegionId,
  regExtValue  Reg-RestrictionUserType-regExtValue
}
Reg-RestrictionUserType-regExtValue ::= CHOICE {
  addGrpC  RestrictionUserType-addGrpC,
  ...
}

Reg-RoadSegment ::= SEQUENCE {
  regionId  RegionId,
  regExtValue  Reg-RoadSegment-regExtValue
}
Reg-RoadSegment-regExtValue ::= CHOICE { ... }

Reg-RTCMcorrections ::= SEQUENCE {
  regionId  RegionId,
  regExtValue  Reg-RTCMcorrections-regExtValue
}
Reg-RTCMcorrections-regExtValue ::= CHOICE { ... }

Reg-SignalControlZone ::= SEQUENCE {
  regionId  RegionId,
  regExtValue  Reg-SignalControlZone-regExtValue
}
Reg-SignalControlZone-regExtValue ::= CHOICE { ... }

Reg-SignalRequest ::= SEQUENCE {
  regionId  RegionId,
  regExtValue  Reg-SignalRequest-regExtValue
}
Reg-SignalRequest-regExtValue ::= CHOICE { ... }

Reg-SignalRequestMessage ::= SEQUENCE {
  regionId  RegionId,
  regExtValue  Reg-SignalRequestMessage-regExtValue
}
Reg-SignalRequestMessage-regExtValue ::= CHOICE { ... }

Reg-SignalRequestPackage ::= SEQUENCE {
  regionId  RegionId,
  regExtValue  Reg-SignalRequestPackage-regExtValue
}
Reg-SignalRequestPackage-regExtValue ::= CHOICE { ... }

Reg-SignalStatus ::= SEQUENCE {
  regionId  RegionId,
  regExtValue  Reg-SignalStatus-regExtValue
}
Reg-SignalStatus-regExtValue ::= CHOICE { ... }

Reg-SignalStatusMessage ::= SEQUENCE {
  regionId  RegionId,
  regExtValue  Reg-SignalStatusMessage-regExtValue
}
Reg-SignalStatusMessage-regExtValue ::= CHOICE { ... }

Reg-SignalStatusPackage ::= SEQUENCE {
  regionId  RegionId,
  regExtValue  Reg-SignalStatusPackage-regExtValue
}
Reg-SignalStatusPackage-regExtValue ::= CHOICE {
  addGrpC  SignalStatusPackage-addGrpC,
  ...
}

Reg-SPAT ::= SEQUENCE {
  regionId  RegionId,
  regExtValue  Reg-SPAT-regExtValue
}
Reg-SPAT-regExtValue ::= CHOICE { ... }

END
