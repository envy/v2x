--FIXME RGY moved here from file SPAT_MAP_ISO_TS_19091.asn

-- ^-^-^-^-^-^-^-^-^-^-^-^-^-^-^-^-^-^-^-^-^-^-^-^-^-^-^-^-
-- 
-- module: AddGrpC
-- ISO TS 19091 30.08.2016
-- 
-- ^-^-^-^-^-^-^-^-^-^-^-^-^-^-^-^-^-^-^-^-^-^-^-^-^-^-^-^-
--FIXME RGY definitions are moved here from AddGrpC; created to cut circular import loops amongst ASN.1 files
AddGrpC-noCircular { iso (1) standard (0) signalizedIntersection (19091) profilec(2) addgrpc (0) version (1) }


DEFINITIONS AUTOMATIC TAGS::= BEGIN 
IMPORTS;

Control-addGrpC ::=  SEQUENCE {
	ptvRequest			PtvRequestType,
	...
}

PtvRequestType	::= ENUMERATED {
	preRequest,
	mainRequest,
	doorCloseRequest,
	cancelRequest,
	emergencyRequest,
	...
}

END
