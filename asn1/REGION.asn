-- ~~~~~~~~~~~~~~~~~~~~~~~~~~~~~~~~~~~~~~~~~~~~~~~~~~~~~~~~~~~~~~~~~~~~~~~~~~~~~~~~~~~~
-- ISO TS 19091
--
-- This ASN.1 was generated: 30.08.2016
--
-- This document contains the data element needed for the encoding the SPAT, MapData, SignalRequestMessage, SignalStatusMessage message
-- as defined in ISO TS 19091 and SAEJ2735
--
-- ~~~~~~~~~~~~~~~~~~~~~~~~~~~~~~~~~~~~~~~~~~~~~~~~~~~~~~~~~~~~~~~~~~~~~~~~~~~~~~~~~~~~

-- ^-^-^-^-^-^-^-^-^-^-^-^-^-^-^-^-^-^-^-^-^-^-^-^-^-^-^-^-
-- 
-- module: REGION
-- 
-- ^-^-^-^-^-^-^-^-^-^-^-^-^-^-^-^-^-^-^-^-^-^-^-^-^-^-^-^-

REGION {iso (1) standard (0) signalizedIntersection (19091) profilec (2) region (1) version2 (2)}

DEFINITIONS AUTOMATIC TAGS::= BEGIN 

IMPORTS
--FIXME RGY definitions moved to non-circularity module
--addGrpC, REG-EXT-ID-AND-TYPE    FROM DSRC
NodeAttributeSet-addGrpC, addGrpC, REG-EXT-ID-AND-TYPE    FROM DSRC-REGION-noCircular
--FIXME RGY NodeAttributeSet-addGrpC has been moved to a non-circularity module
--NodeAttributeSet-addGrpC FROM AddGrpC-noCircular
ConnectionManeuverAssist-addGrpC, ConnectionTrajectory-addGrpC, IntersectionState-addGrpC, /*NodeAttributeSet-addGrpC,*/  Position3D-addGrpC, RestrictionUserType-addGrpC, LaneAttributes-addGrpC, MovementEvent-addGrpC, RequestorDescription-addGrpC, 
SignalStatusPackage-addGrpC, MapData-addGrpC  FROM AddGrpC {iso (1) standard (0) signalizedIntersection (19091) profilec (2) addgrpc (0) version2 (2)};


Reg-AdvisorySpeed					REG-EXT-ID-AND-TYPE ::= { ... }

Reg-ComputedLane					REG-EXT-ID-AND-TYPE ::= { ... }

Reg-ConnectionManeuverAssist	REG-EXT-ID-AND-TYPE ::= { 
	{ConnectionManeuverAssist-addGrpC	IDENTIFIED BY addGrpC} ,
	... 
}

Reg-GenericLane           REG-EXT-ID-AND-TYPE ::= {
	{ConnectionTrajectory-addGrpC	IDENTIFIED BY addGrpC} ,
	... 
}

Reg-IntersectionGeometry  REG-EXT-ID-AND-TYPE ::= { ...  }

Reg-IntersectionState     REG-EXT-ID-AND-TYPE ::= {
	{IntersectionState-addGrpC IDENTIFIED BY addGrpC} ,
	...
}

Reg-LaneAttributes	             REG-EXT-ID-AND-TYPE ::= {
   {LaneAttributes-addGrpC IDENTIFIED BY addGrpC} ,
   ...
}

/*FIXME RGY moved to IS-DSRC-REGION-noCircular to cut circular import loop
Reg-LaneDataAttribute     	REG-EXT-ID-AND-TYPE ::= { ... }
*/

Reg-MapData								REG-EXT-ID-AND-TYPE ::= { 
    {MapData-addGrpC  IDENTIFIED BY addGrpC},
    ...
}

Reg-MovementEvent	            REG-EXT-ID-AND-TYPE ::= {
   {MovementEvent-addGrpC IDENTIFIED BY addGrpC} ,
   ...
}

Reg-MovementState         	REG-EXT-ID-AND-TYPE ::= { ...  }

-- Reg-NodeAttributeSetLL       REG-EXT-ID-AND-TYPE ::= { ... }

/*FIXME RGY moved to IS-DSRC-REGION-noCircular to cut circular import loop
Reg-NodeAttributeSetXY    	REG-EXT-ID-AND-TYPE ::= {
	{NodeAttributeSet-addGrpC	IDENTIFIED BY addGrpC} ,
	 ...
}
*/

-- Reg-NodeOffsetPointLL	   REG-EXT-ID-AND-TYPE ::= { ... }

/*FIXME RGY moved to IS-DSRC-REGION-noCircular to cut circular import loop
Reg-NodeOffsetPointXY     	REG-EXT-ID-AND-TYPE ::= { ... }
*/

Reg-Position3D            		REG-EXT-ID-AND-TYPE ::= {
	{Position3D-addGrpC IDENTIFIED BY addGrpC} ,
	...
}

Reg-RequestorDescription      REG-EXT-ID-AND-TYPE ::= {
   { RequestorDescription-addGrpC IDENTIFIED BY addGrpC} ,
   ...
}

Reg-RequestorType         	REG-EXT-ID-AND-TYPE ::= { ...  }

Reg-RestrictionUserType   	REG-EXT-ID-AND-TYPE ::= { 
	{RestrictionUserType-addGrpC IDENTIFIED BY addGrpC} ,
	...
}

Reg-RoadSegment						REG-EXT-ID-AND-TYPE ::= { ...  }

Reg-RTCMcorrections             REG-EXT-ID-AND-TYPE ::= { ... }

Reg-SignalControlZone				REG-EXT-ID-AND-TYPE ::= { ...  }

Reg-SignalRequest					REG-EXT-ID-AND-TYPE ::= { ...  }

Reg-SignalRequestMessage			REG-EXT-ID-AND-TYPE ::= { ... }

Reg-SignalRequestPackage			REG-EXT-ID-AND-TYPE ::= { ...  }

Reg-SignalStatus					REG-EXT-ID-AND-TYPE ::= { ...  }

Reg-SignalStatusMessage				REG-EXT-ID-AND-TYPE ::= { ... }

Reg-SignalStatusPackage   	REG-EXT-ID-AND-TYPE ::= { 
	{ SignalStatusPackage-addGrpC IDENTIFIED BY addGrpC} ,
	...
}

Reg-SPAT                            REG-EXT-ID-AND-TYPE ::= { ... }

END
