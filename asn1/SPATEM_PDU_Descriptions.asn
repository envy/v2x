-- ^-^-^-^-^-^-^-^-^-^-^-^-^-^-^-^-^-^-^-^-^-^-^-^-^-^-^-^-
-- 
-- module: SPAT-MESSAGE-PDU-Descriptions
-- 
-- This ASN.1 was created: 30.08.2016
--
-- ^-^-^-^-^-^-^-^-^-^-^-^-^-^-^-^-^-^-^-^-^-^-^-^-^-^-^-^-

SPATEM-PDU-Descriptions {
  itu-t (0) identified-organization (4) etsi (0) itsDomain (5)  wg1 (1) en (103301) spatem (0) version2 (2)
}

DEFINITIONS AUTOMATIC TAGS ::= 

BEGIN

IMPORTS
SPAT FROM DSRC { iso (1) standard (0) signalizedIntersection (19091) profilec(2) dsrc (2) version2 (2) }
ItsPduHeader FROM ITS-Container { itu-t (0) identified-organization (4) etsi (0) itsDomain (5) wg1 (1) ts (102894) cdd (2) version (2) }

;
-- End of IMPORTS

SPATEM ::= SEQUENCE {
	header	ItsPduHeader,
	spat	SPAT
}

END
